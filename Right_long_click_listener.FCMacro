import time
from PySide import QtCore, QtWidgets
import FreeCAD as App
import FreeCADGui as Gui

# --- CONFIGURATION ---
# Set the time required (in seconds) to trigger the long-click command
LONG_CLICK_THRESHOLD = 0.400  

def long_click_command():
    """
    Define what your long right-click does here.
    Example: Opens the 'Fit All' view command.
    """
    App.Console.PrintMessage("Long right-click detected! Executing command...\n")
    Gui.runCommand("Std_ViewFitAll")


class GlobalLongClickFilter(QtCore.QObject):
    def __init__(self):
        super(GlobalLongClickFilter, self).__init__()
        self.press_time = 0.0

    def eventFilter(self, watched, event):
        # 1. Detect mouse press
        if event.type() == QtCore.QEvent.MouseButtonPress:
            if event.button() == QtCore.Qt.RightButton:
                # Target interactions happening over the core 3D Canvas elements
                class_name = watched.metaObject().className()
                if "View3D" in class_name or "GL" in class_name or "graphicsView" in watched.objectName():
                    self.press_time = time.time()
                return False  # Let FreeCAD process normal dragging/panning rotation

        # 2. Detect mouse release
        elif event.type() == QtCore.QEvent.MouseButtonRelease:
            if event.button() == QtCore.Qt.RightButton and self.press_time > 0:
                duration = time.time() - self.press_time
                self.press_time = 0.0  # Reset counter
                
                if duration >= LONG_CLICK_THRESHOLD:
                    long_click_command()
                    return True  # Consume the release event to block the standard context menu

        return super(GlobalLongClickFilter, self).eventFilter(watched, event)


# --- INITIALIZATION & CLEANUP ---
def install_global_filter():
    global _global_mouse_filter_instance
    
    # Safely fetch the core application instantiation container
    app_instance = QtWidgets.QApplication.instance()
    
    if not app_instance:
        App.Console.PrintError("Error: Could not retrieve the main Qt application context.\n")
        return

    # Clean up any legacy active instances to avoid duplicate event calls
    try:
        if '_global_mouse_filter_instance' in globals():
            app_instance.removeEventFilter(_global_mouse_filter_instance)
    except Exception:
        pass

    # Instantiate and install across the global event loop
    _global_mouse_filter_instance = GlobalLongClickFilter()
    app_instance.installEventFilter(_global_mouse_filter_instance)
    App.Console.PrintMessage("Success: Global long right-click listener activated seamlessly!\n")

# Run execution
install_global_filter()
